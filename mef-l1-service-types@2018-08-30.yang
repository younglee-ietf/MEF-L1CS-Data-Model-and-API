module mef-l1-service-types {
  namespace "urn:mef:params:xml:ns:yang:mef-l1-service-types";
  prefix "l1-st";

  organization
	 "MEF L1CS Data Model Project";
  contact
	"Editor: G. Fioccolla(giuseppe.fioccola@telecomitalia.it)
	 Editor: K. Lee (kwangkoog.lee@kt.com)
	 Editor: Y. Lee (leeyoung@huawei.com)
	 Editor: D. Dhody (dhruv.ietf@gmail.com)
	 Editor: O. G. de-Dios(oscar.gonzalezdedios@telefonica.com)
	 Editor: D. Ceccarelli(daniele.ceccarelli@ericsson.com)";

  description
     "This module defines L1 service types based on MEF 63: 
     Subscriber Layer 1 Service Attribute Technical Specification.
     Refer to MEF 63 for all terms and the original references 
     used in the module. As for the protocol-type, refer also to
     the client-type in G.709.";
  
     revision "2018-08-30" {
       description "Initial revision.";
       reference "MEF XXXX: A Yang Data Model for L1 Connectivity 
                 Service Model (L1CSM)";
     }  


    identity protocol-type {
	description 
	"base identity from which client protocol type is derived.";
	}
	
	identity ETH-1GbE {
		base "protocol-type";
		description
		    "GigE protocol type";
		reference "MEF63 & G.709";
	}
	
	identity ETH-10GbE-WAN {
		base "protocol-type";
		description
			"10GigE-WAN protocol type";
	    reference "MEF63 & G.709";
	}
	
	identity ETH-10GbE-LAN {
		base "protocol-type";
		description
			"10GigE-LAN protocol type";
		reference "MEF63 & G.709";
	}
	
	identity ETH-40GbE {
		base "protocol-type";
		description
			"40GigE protocol type";
		reference "MEF63 & G.709";
	}
	
	identity ETH-100GbE {
		base "protocol-type";
		description
			"100GigE protocol type";
		reference "MEF63 & G.709";
	}
	
	identity FC-100 {
		base "protocol-type";
		description
			"Fiber Channel - 100 protocol type";
		reference "MEF63 & G.709";
	}
	
	identity FC-200 {
		base "protocol-type";
		description
			"Fiber Channel - 200 protocol type";
		reference "MEF63 & G.709";
	}
	
	identity FC-400 {
		base "protocol-type";
		description
			"Fiber Channel - 400 protocol type";
		reference "MEF63 & G.709";
	}
	
	identity FC-800 {
		base "protocol-type";
		description
			"Fiber Channel - 800 protocol type";
		reference "MEF63 & G.709";
	}
	
	identity FC-1200 {
		base "protocol-type";
		description
			"Fiber Channel - 1200 protocol type";
		reference "MEF63 & G.709";
	}
	
	identity FC-1600 {
		base "protocol-type";
		description
			"Fiber Channel - 1600 protocol type";
		reference "MEF63 & G.709";
	}
	
	identity FC-3200 {
		base "protocol-type";
		description
			"Fiber Channel - 3200 protocol type";
		reference "MEF63 & G.709";
	}
	
	identity STM-1 {
		base "protocol-type";
		description
			"SDH STM-1 protocol type";
		reference "MEF63 & G.709";
	}
	
	identity STM-4 {
		base "protocol-type";
		description
			"SDH STM-4 protocol type";
		reference "MEF63 & G.709";
	}
	
	identity STM-16 {
		base "protocol-type";
		description
			"SDH STM-16 protocol type";
		reference "MEF63 & G.709";
	}
	
	identity STM-64 {
		base "protocol-type";
		description
			"SDH STM-64 protocol type";
		reference "MEF63 & G.709";
	}
	
	identity STM-256 {
		base "protocol-type";
		description
			"SDH STM-256 protocol type";
		reference "MEF63 & G.709";
	}
	
	identity OC-3 {
		base "protocol-type";
		description
			"SONET OC-3 protocol type";
		reference "MEF63 & G.709";
	}
	
	identity OC-12 {
		base "protocol-type";
		description
			"SONET OC-12 protocol type";
		reference "MEF63 & G.709";
	}
	
	identity OC-48 {
		base "protocol-type";
		description
			"SONET OC-48 protocol type";
		reference "MEF63 & G.709";
	}
	
	identity OC-192 {
		base "protocol-type";
		description
			"SONET OC-192 protocol type";
		reference "MEF63 & G.709";
	}
	
	identity OC-768 {
		base "protocol-type";
		description
			"SONET OC-768 protocol type";
		reference "MEF63 & G.709";
	}
	
  identity coding-func {
	description 
	"base identity from which coding func is derived.";
  }
	
	identity ETH-1000X-PCS-36 {
		base "coding-func";
		description
			"PCS clause 36 coding function that corresponds to 1000BASE-X";
	}
	
	identity ETH-10GW-PCS-49-WIS-50 {
		base "coding-func";
		description
			"PCS clause 49 and WIS clause 50 coding func that corresponds to 10GBASE-W (WAN PHY)";
	}
	
	identity ETH-10GR-PCS-49 {
		base "coding-func";
		description
			"PCS clause 49 coding function that corresponds to 10GBASE-R (LAN PHY)";
	}
	
	identity ETH-40GR-PCS-82 {
		base "coding-func";
		description
			"PCS clause 82 coding function that corresponds to 40GBASE-R";
	}
	
	identity ETH-100GR-PCS-82 {
		base "coding-func";
		description
			"PCS clause 82 coding function that corresponds to 100GBASE-R";
	}
	
	/* coding func needs to expand for Fiber Channel, SONET, SDH  */
	

        identity optical-interface-func {
	   description 
	   "base identity from which optical-interface-function is derived.";
        } 
	
	identity SX-PMD-clause-38 {
		base "optical-interface-func";
		description 
			"SX-PMD-clause-38 Optical Interface function for 1000BASE-X PCS-36"; 
	}
	
	identity LX-PMD-clause-38 {
		base "optical-interface-func";
		description
			"LX-PMD-clause-38 Optical Interface function for 1000BASE-X PCS-36"; 
	}
	
	identity LX10-PMD-clause-59 {
		base "optical-interface-func";
		description
			"LX10-PMD-clause-59 Optical Interface function for 1000BASE-X PCS-36"; 
	}
	
	identity BX10-PMD-clause-59 {
		base "optical-interface-func";
		description
			"BX10-PMD-clause-59 Optical Interface function for 1000BASE-X PCS-36"; 
	}
	
	identity LW-PMD-clause-52 {
		base "optical-interface-func";
		description
			"LW-PMD-clause-52 Optical Interface function for 10GBASE-W PCS-49-WIS-50"; 
	}
	
	identity EW-PMD-clause-52 {
		base "optical-interface-func";
		description
			"EW-PMD-clause-52 Optical Interface function for 10GBASE-W PCS-49-WIS-50"; 
	}
	
	identity LR-PMD-clause-52 {
		base "optical-interface-func";
		description
			"LR-PMD-clause-52 Optical Interface function for 10GBASE-R PCS-49"; 
	}
	
	identity ER-PMD-clause-52 {
		base "optical-interface-func";
		description
			"ER-PMD-clause-52 Optical Interface function for 10GBASE-R PCS-49"; 
	}
	
	identity LR4-PMD-clause-87 {
		base "optical-interface-func";
		description
			"LR4-PMD-clause-87 Optical Interface function for 40GBASE-R PCS-82"; 
	}
	
	identity ER4-PMD-clause-87 {
		base "optical-interface-func";
		description
			"ER4-PMD-clause-87 Optical Interface function for 40GBASE-R PCS-82"; 
	}
	
	identity FR-PMD-clause-89 {
		base "optical-interface-func";
		description
			"FR-PMD-clause-89 Optical Interface function for 40GBASE-R PCS-82"; 
	}
	
	identity LR4-PMD-clause-88 {
		base "optical-interface-func";
		description
			"LR4-PMD-clause-88 Optical Interface function for 100GBASE-R PCS-82"; 
	}
	
	identity ER4-PMD-clause-88 {
		base "optical-interface-func";
		description
			"ER4-PMD-clause-88 Optical Interface function for 100GBASE-R PCS-82"; 
	}
	
	/* optical interface func needs to expand for Fiber Channel, SONET and SDH */
	

        identity performance-metriclist {
	   description "list of performance metric";
        }
	
	identity One-way-Delay {
		base "performance-metriclist";
		description "one-way-delay";	
	}
	
	identity One-way-Errored-Second {
		base "performance-metriclist";
		description "one-way-errored-second";	
	}
	
	identity One-way-Severely-Errored-Second {
		base "performance-metriclist";
		description "one-way-severely-errored-second";	
	}
	
	identity One-way-Unavailable-Second {
		base "performance-metriclist";
		description "one-way-unavailable-second";	
	}

	identity One-way-Availability {
		base "performance-metriclist";
		description "one-way-availability";	
	}
	

}
